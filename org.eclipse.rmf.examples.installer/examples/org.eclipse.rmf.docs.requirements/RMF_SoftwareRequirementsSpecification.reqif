# Specification: Specification Document
- Description: Software Requirements Specification

## sws_0001: Naming conventions and Definitions (Headline Type)

## sws_0002: Relevant Facts and Assumptions (Headline Type)

## sws_0003: Scope (Headline Type)

## sws_0004: Functional and Data Requirements (Headline Type)

### sws_0005: Functional Requirements (Headline Type)

#### sws_0006: RMF as Importer / Exporter (Headline Type)

#### sws_0007: RMF as ReqIF Editor (Headline Type)

#### sws_0008: RMF as Backend of Requirements management Tools (Requirement Type)

#### sws_0009: Automatic set of internal IDs (Requirement Type)

#### sws_0010: Automatic set of lastModifiedDate (Requirement Type)

#### sws_0011: ReqIF XSD schema validation (Requirement Type)

#### sws_26: ReqIF semantic constraints validation (Requirement Type)

### sws_46: Data Requirements (Headline Type)

#### sws_10: Metamodel may be more powerful than required by ReqIF standard (Requirement Type)

#### sws_11: Allow flexible separation on files (Requirement Type)
- Rationale: Reuse of datatypes and spectypes for multiple reqif files. Finegrained partitioning for file based version control

#### sws_13: Support XHTML entities (Requirement Type)
RMF shall translate XHTML entities such as '&ouml;' during desrialization into proper UTF-8 characters
- Rationale: Allows copying of XHTML that often contain HTML entities into ReqIF files

## sws_28: Look and Feel Requirements (Headline Type)

### sws_20: error handling shall clearly distinguish between errors that are related to incorrect integration and error that are related to the data which can be fixed by the end user (Requirement Type)

## sws_29: Usability Requirements (Headline Type)

### sws_30: Ease of Use (Headline Type)

### sws_31: Ease of Learning (Headline Type)

## sws_32: Performance Requirements (Headline Type)

### sws_33: Speed Requirements (Headline Type)

#### sws_14: Optimized for scalability (Requirement Type)
RMF shall be able to read and write files with a size of 100MB ReqIF XML size without running into out of memory

#### sws_27: Optimized for performance (Requirement Type)

### sws_34: Safety Critical Requirements (Headline Type)

#### sws_8: No modifications without intention of the user (Requirement Type)
RMF shall not modify ReqIF files without the intention of the user while reading and writing
- Rationale: Avoid unintended modifications such as changing id, adding / removing line breaks, etc.
- Notes: This includes not to remove or modify tool extensions
- Author: Mark Brörkens

##### sws_49: Preserve order of elements (Requirement Type)
RMF shall preserve the order of XML elements whil reading and writing ReqIF files
- Rationale: Simplify manual / automatic diff

##### sws_50: Preserve tool extensions (Requirement Type)
RMF shall preserve the content of tool extensions

##### sws_51: Preserve semantic value of data (Requirement Type)
RMF shall preserve the semantic value of datatypes

##### sws_52: Preserve identifiers (Requirement Type)
RMF shall preserve existing identifiers that are contained in reqif file. If identifiers are missing, RMF may set them.
- Rationale: Ensure that contents of reqif files that are edited by RMF are still linkable without the need for reading or updating the specrelations.

### sws_35: Precision Requirements (Headline Type)

#### sws_48: new req (Requirement Type)

### sws_36: Reliability and Availability Requirements (Headline Type)

#### sws_47: Raise errors for incorrect data (Requirement Type)

### sws_37: Capacity Requirements (Headline Type)

## sws_38: Operational Requirements (Headline Type)

### sws_40: Expected Physical Environment (Headline Type)

### sws_39: Expected Technological Environment (Headline Type)

#### sws_3: Support current and previous Eclipse Release (Requirement Type)
RMF shall support the current and the previous Eclipse Release
- Rationale: maximize the supported platforms
- Author: Mark Brörkens
- Status: NEW

#### sws_4: Executable with oldest Java version required by Eclipse targets (Requirement Type)
RMF shall run with the oldest  Java version that is required by the previous Eclipse release
- Rationale: maximize the supported platforms
- Author: Mark Brörkens
- Status: NEW

#### sws_5: Executable without Eclipse Runtime (Requirement Type)
The RMF metamodel, serialization and validation shall run without Eclipse Runtime
- Rationale: allow usage of RMF for adding ReqIF support to Non-Eclipse Tools or simple generator scripts
- Author: Mark Brörkens
- Status: NEW

#### sws_6: Execution Environment Headless Eclipse (Requirement Type)
- Author: Mark Brörkens

#### sws_7: Execution Environment Eclipse with UI (Requirement Type)
- Author: Mark Brörkens

#### sws_12: Focus on common EMF techniques (Requirement Type)
- Notes: Avoid need for support of FeatureMaps.

#### sws_15: Enable usage in many contexts (Requirement Type)

#### sws_24: may expect validating and namespace aware parser (Requirement Type)

### sws_41: Partner Applications (Headline Type)

#### sws_16: usage with sample reflective editor (Requirement Type)

#### sws_17: usage of tool extensions with provided schema (Requirement Type)

#### sws_18: usage of tool extensions with provided emf classes (Requirement Type)

#### sws_19: usage of tool extensions with provided emf package as ecore file (Requirement Type)

#### sws_25: XHTML as string (Requirement Type)

#### sws_23: allow usage of RMF parts in standard contexts (Requirement Type)
- Notes: e.g. allow usage of RMF Resource in a standard ResourceSet. Should be possible, however cross file references will not be resolved.

#### sws_22: provide set of standard EMF plugins that allow reuse and many contexts (Requirement Type)

#### sws_21: Allow alternative storages (Requirement Type)
- Notes: E.g. CDO, Binary

## sws_42: Maintainability and Portability Requirements (Headline Type)

### sws_9: Reuse of Serialization component (Requirement Type)
The RMF serialization shall be reusable for all RMF metamodels and metamodels that are not part of RMF
- Notes: ReqIF serialization is based on the default AUTOSAR serialization mechanisms which are not configurable by Extended Metadata or other load and safe options using the standard EMF serialization mechanism. Other projects such as EATOP have shown interest in reusing the RMF serialization
- Rationale: Extend the amount of users and contributors in order to improve the robustness and performance of the serialization
- Author: Mark Brörkens

### sws_2: No warnings in code (Requirement Type)

## sws_43: Security Requirements (Headline Type)

## sws_44: Cultural and Political Requirements (Headline Type)

## sws_45: Legal Requirements (Headline Type)
