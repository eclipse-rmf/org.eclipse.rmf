# Specification: Specification Document
- Description: Software Requirements Specification

## sws_0001: Naming conventions and Definitions (Headline Type)

## sws_0002: Relevant Facts and Assumptions (Headline Type)

## sws_0003: Scope (Headline Type)

## sws_0004: Functional and Data Requirements (Headline Type)

### sws_0005: Functional Requirements (Headline Type)

#### sws_0006: RMF as Importer / Exporter (Headline Type)

#### sws_0007: RMF as Requirements Management Tool Backend (Headline Type)

#### sws_0008: RMF as Backend of Requirements management Tools (Requirement Type)

#### sws_0009: Automatic set of internal IDs (Requirement Type)

#### sws_0010: Automatic set of lastModifiedDate (Requirement Type)

#### sws_0011: ReqIF XSD schema validation (Requirement Type)

#### R29: ReqIF semantic constraints validation (Requirement Type)

### R54: Data Requirements (Headline Type)

#### R10: Metamodel may be more powerful than required by ReqIF standard (Requirement Type)

#### R13: Allow flexible separation on files (Requirement Type)
- Rationale: Reuse of datatypes and spectypes for multiple reqif files. Finegrained partitioning for file based version control

#### R15: Support XHTML entities (Requirement Type)

## R35: Look and Feel Requirements (Headline Type)

### R22: error handling shall clearly distinguish between errors that are related to incorrect integration and error that are related to the data which can be fixed by the end user (Requirement Type)

## R36: Usability Requirements (Headline Type)

### R37: Ease of Use (Headline Type)

### R38: Ease of Learning (Headline Type)

## R39: Performance Requirements (Headline Type)

### R40: Speed Requirements (Headline Type)

#### R16: Optimzed for performance and scalability (Requirement Type)

#### R30: Optimized for performance (Requirement Type)

### R41: Safety Critical Requirements (Headline Type)

#### R6: No modifications without intention of the user (Requirement Type)
RMF shall not modify ReqIF files without the intention of the user while reading and writing
- Rationale: Avoid unintended modifications such as changing id, adding / removing line breaks, etc.
- Notes: This includes not to remove or modify tool extensions
- Author: Mark Brörkens

### R42: Precision Requirements (Headline Type)

### R43: Reliability and Availability Requirements (Headline Type)

#### R55: Raise errors for incorrect data (Requirement Type)

### R44: Capacity Requirements (Headline Type)

## R45: Operational Requirements (Headline Type)

### R47: Expected Physical Environment (Headline Type)

### R46: Expected Technological Environment (Headline Type)

#### R1: Support current and previous Eclipse Release (Requirement Type)
RMF shall support the current and the previous Eclipse Release
- Rationale: maximize the supported platforms
- Author: Mark Brörkens
- Status: NEW

#### R2: Executable with oldest Java version required by Eclipse targets (Requirement Type)
RMF shall run with the oldest  Java version that is required by the previous Eclipse release
- Rationale: maximize the supported platforms
- Author: Mark Brörkens
- Status: NEW

#### R3: Executable without Eclipse Runtime (Requirement Type)
The RMF metamodel, serialization and validation shall run without Eclipse Runtime
- Rationale: allow usage of RMF for adding ReqIF support to Non-Eclipse Tools or simple generator scripts
- Author: Mark Brörkens
- Status: NEW

#### R4: Execution Environment Headless Eclipse (Requirement Type)
- Author: Mark Brörkens

#### R5: Execution Environment Eclipse with UI (Requirement Type)
- Author: Mark Brörkens

#### R14: Focus on common EMF techniques (Requirement Type)
- Notes: Avoid need for support of FeatureMaps.

#### R17: Enable usage in many contexts (Requirement Type)

#### R26: may expect validating and namespace aware parser (Requirement Type)

### R48: Partner Applications (Headline Type)

#### R18: usage with sample reflective editor (Requirement Type)

#### R19: usage of tool extensions with provided schema (Requirement Type)

#### R20: usage of tool extensions with provided emf classes (Requirement Type)

#### R21: usage of tool extensions with provided emf package as ecore file (Requirement Type)

#### R27: XHTML as string (Requirement Type)

#### R25: allow usage of RMF parts in standard contexts (Requirement Type)
- Notes: e.g. allow usage of RMF Resource in a standard ResourceSet. Should be possible, however cross file references will not be resolved.

#### R24: provide set of standard EMF plugins that allow reuse and many contexts (Requirement Type)

#### R23: Allow alternative storages (Requirement Type)
- Notes: E.g. CDO, Binary

## R49: Maintainability and Portability Requirements (Headline Type)

### R7: Reuse of Serialization component (Requirement Type)
The RMF serialization shall be reusable for all RMF metamodels and metamodels that are not part of RMF
- Notes: ReqIF serialization is based on the default AUTOSAR serialization mechanisms which are not configurable by Extended Metadata or other load and safe options using the standard EMF serialization mechanism. Other projects such as EATOP have shown interest in reusing the RMF serialization
- Rationale: Extend the amount of users and contributors in order to improve the robustness and performance of the serialization
- Author: Mark Brörkens

### sws_2: No warnings in code (Requirement Type)

## R50: Security Requirements (Headline Type)

## R51: Cultural and Political Requirements (Headline Type)

## R52: Legal Requirements (Headline Type)
