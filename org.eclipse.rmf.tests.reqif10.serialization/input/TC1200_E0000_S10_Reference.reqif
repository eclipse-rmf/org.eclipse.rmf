# TC 1200 'Formated Content'

# Specification

## R1
- TC1200 AttributeDefinitionString: xhtml.a.type
- TC1200 AttributeDefinitionXHTML: XhtmlPType text before br
  text after br text before spanXhtmlSpanTypetext after span text before emXhtmlEmTypetext after em text before strongXhtmlStrongTypetext after strong text before dfnXhtmlDfnTypetext after dfn text before codeXhtmlCodeTypetext after code text before sampXhtmlSampTypetext after samp text before kbdXhtmlKbdTypetext after kbd text before varXhtmlVarTypetext after var text before citeXhtmlCiteTypetext after cite text before abbrXhtmlAbbrTypetext after abbr text before acronymXhtmlAcronymTypetext after acronym text before qXhtmlQTypetext after q text before ttXhtmlInlPresTypetext after tt text before iXhtmlInlPresTypetext after i text before bXhtmlInlPresTypetext after b text before bigXhtmlInlPresTypetext after big text before smallXhtmlInlPresTypetext after small text before sub_XhtmlInlPresTypetext after sub text before sup^XhtmlInlPresTypetext after sup text before insXhtmlEditTypetext after ins text before delXhtmlEditTypetext after del
