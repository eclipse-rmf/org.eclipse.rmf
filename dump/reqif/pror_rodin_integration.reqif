# Specification: Specification Document

## Drag and Drop (Headline Type)

### UC DND CREATE TRACE (Use Case Type)
- Main Success Scenario:
  1. The user selects the model element in the outline view of the Event-B editor.
  
  2. The user drags the model element (target) and drops it to the corresponding artifact (source).
  
  3. ProR locates the proxy model element for the model element, or creates one if it does not exist yet.
  
  4. ProR creates a trace/link between the proxy model element and the artifact.
- Precondition: At least one artifact and one model element exists.
- Guarantee: A proxy model element is created (if does not exist yet) and a trace between the artifact and the model element is established.
- Exceptions: Trace already exists. In this case nothing happens.
- Actors: User, ProR
- Variation: -

### UC DND EDIT MODEL ELEMENT (Use Case Type)
- Guarantee: The proxy model element is updated.
- Main Success Scenario:
  1. The user edits a model element (i.e. an invariant).
  
  2. ProR updates the corresponding proxy model element upon save of the Event-B editor.
- Actors: User, ProR
- Exceptions: Note that ProR can only react to model changes if the ReqIF model is open, while the Event-B model is being edited.
  See: UC-DND-OPEN-REQIF-MODEL
- Precondition:
  - A corresponding proxy model element of the edited model element exists.
  
  - ProR is open.
- Variation: -

### UC DND DELETE MODEL FILE (Use Case Type)
- Guarantee: -
- Main Success Scenario:
  1. The user deletes a model element.
  
  2. ProR marks the proxy model element as “missing”.
- Actors: User, ProR
- Exceptions: Note that ProR can only react to model changes if the ReqIF model is open, while the Event-B model is being edited.
  See: UC-DND-OPEN-REQIF-MODEL
- Precondition: ProR is open
- Variation: The user deletes a model file (i.e. machine or context file): In this case all linked model elements of the model file are marked as “missing”.

### UC RENAME MODEL FILE (Use Case Type)
- Guarantee: -
- Main Success Scenario:
  1. The user renames a model file (i.e. machine or context file).
  
  2. ProR updates the references of the proxy model elements.
- Variation: -
- Actors: User, ProR
- Exceptions: Note that ProR can only react to model changes if the ReqIF model is open, while the Event-B model is being edited.
  See: UC-DND-OPEN-REQIF-MODEL
- Precondition: -

### UC DND OPEN REQIF MODEL (Use Case Type)
- Guarantee: Changes in the model have been detected and acted upon.
- Main Success Scenario:
  1.  The user opens a ReqIF model.
  
  2. ProR detects changes made in the model.
  
  3. ProR updates the affected proxy model elements (See also: UC-DND-EDIT-MODEL-ELEMENT and UC-DND-DELETE-MODEL-FILE).
  
  4. ProR marks the proxy model elements which are not found in the Event-B model as “missing”.
- Variation: -
- Actors: User, ProR
- Precondition: The model files exists under the same names as referenced in the proxy model elements and the ProR editor is closed.

## Color Highlighting (Headline Type)

### UC COLOR HIGHLIGHTING (Use Case Type)
- Guarantee: The model element names in the artifact attribute (i.e. description) are highlighted.
- Main Success Scenario:
  1. The user enters the name of a model element (in square brackets) in an artifact attribute (i.e. description).
  
  2. ProR highlights the model element name in the artifact attribute (i.e. description).
  
  Scenario # Renderer # Editor
  name not marked # black text # red underline
  marked & exists # blue text # blue text
  marked & does not exist # red text # red text
- Variation: -
- Actors: User, ProR
- Exceptions: Note that ProR can only react to artifact changes which are located outside of the ReqIF model, if the ReqIF model is open.
- Precondition: -

### UC COLOR RENAME MODEL ELEMENT (Use Case Type)
- Guarantee: The highlighted model element names are updated in the artifact attributes (i.e. description).
- Main Success Scenario:
  1. The user renames a model element in the Event-B editor (i.e. a variable).
  
  2. ProR updates the highlighted model element names in the artifact attributes (i.e. description) upon save of the Event-B editor.
- Variation: -
- Actors: User, ProR
- Exceptions:
  - Note that ProR can only react to artifact changes which are located outside of the ReqIF model, if the ReqIF model is open.
  - We get a problem if a variable and constant have the same name.
- Precondition: -

## Link Management (Headline Type)

### UC LINK EDIT REQ (Use Case Type)
- Guarantee: The source or target status attribute of the corresponding traces are set to “changed”.
- Main Success Scenario:
  1. The user edits an artifact (i.e. a requirement).
  
  2. ProR sets the source or target status attribute of the trace(s) to “changed”.
- Variation: If the status attribute of the trace(s) are already set to “changed”, then this use case has no effect.
- Actors: User, ProR
- Exceptions: Note that ProR can only react to artifact changes which are located outside of the ReqIF model, if the ReqIF model is open.
- Precondition: At least one trace between two artifacts exists.

### UC WIZ PROJECT SETUP (Use Case Type)
- Guarantee: A ReqIF model is created with the predefined Event-B specific ReqIF types and presentation configurations.
- Main Success Scenario:
  1. The user opens the Event-B ReqIF File wizard.
  
  2. The user enters a name for the ReqIF file.
  
  3. The user confirms his entries.
  
  4. ProR creates a new ReqIF file with the predefined Event-B specific ReqIF types and presentation configurations.
  
  5. ProR opens the created ReqIF model.
- Variation: -
- Actors: User, ProR
- Exceptions: -

## Phenomena (Headline Type)

### UC PHEN CREATE (Use Case Type)
- Actors: User, ProR
