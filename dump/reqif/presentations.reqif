# Specification: Specification Document
- Description: Refactoring / Cleanup of Presentations

## R1 (Headline Type)
Current Situation

### REQ-1 (Requirement Type)
While the presentation subsystem works, it is not very clean and contains a number of inconsistencies.  In the following, we'll describe how we would design it from scratch (if we could).

## R3 (Headline Type)
Concepts

### R7 (Headline Type)
PresentationService and -Manager

#### REQ-4 (Requirement Type)
For every Presentation, there is one class that manages it (across Projects and ReqIF models).  This is the PresentationService.
- Implementation Status: Implemented

#### REQ-5 (Requirement Type)
The PresentationService is instantiated upon Eclipse Startup
- Implementation Status: lazy by PresentationManager.getPresentationServiceMap()

#### REQ-6 (Requirement Type)
Currently, the PresentationService is notified upon opening and closing.  This does not make sense.  This should move to the Configuration Element

### R8 (Headline Type)
ProrPresentationConfiguration and -Manager

#### REQ-7 (Requirement Type)
Upon creating a configuration object, it should get a chance to register with the ReqIF object.
