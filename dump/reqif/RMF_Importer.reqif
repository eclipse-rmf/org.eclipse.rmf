# Specification: Specification Document
- Description: RMF Importer Specification

## R2 (Headline Type)
ReqIF Importer for ProR Specification

### REQ-1 (Requirement Type)
The Import feature allows users to populate their ReqIF models with data that is not in the ReqIF format.
- links to -> REQ-103

### REQ-2 (Requirement Type)
This feature is crucial, as there are currently very few ReqIF tools on the market. To allow users to explore RMF with their own data, there must be an alternative way of getting data into the system.
- Status: rejected

## R4 (Headline Type)
Architectural Considerations

### REQ-3 (Requirement Type)
There are fundamentally two approaches to import:

#### REQ-5 (Requirement Type)
Provide a quick, but not very powerful way for importing data, by using a widely accepted format (e.g. csv). Such an approach may not support hierarchies, enumerations, etc. But it's easy to implement and easy to use.

#### REQ-6 (Requirement Type)
Provide a sophisticated, powerful import that supports most of the ReqIF features: Such an approach could, for instance, support mapping to Word styles, understand Excel, and would come with a powerful import wizard that allows mapping of data, and in particular would also manage ReqIF data types.

## R8 (Headline Type)
Requirements (Simple Version)

### REQ-7 (Requirement Type)
Support one file format only, but one that user data can easily be "massaged" into (e.g. CSV, XML)
- Status: approved

### REQ-8 (Requirement Type)
Supports a small number of datatypes, maybe only one (at least String, maybe more)

### REQ-9 (Requirement Type)
Supports any number of attributes

### REQ-10 (Requirement Type)
All requirements have the same attributes

### REQ-11 (Requirement Type)
Supports no hierarcies (just a flat list)

## R15 (Headline Type)
Proposed solution

### REQ-12 (Requirement Type)
CSV as the data format (an Excel API is available, but not part of Eclipse, and therefore would reqire a CQ)

### REQ-101 (Requirement Type)
Eine neue Anforderung wird eingefuegt

#### R21 (Headline Type)
Unterüberschrift

### REQ-13 (Requirement Type)
The first row contains the Attribute names

### REQ-14 (Requirement Type)
Supports String data and numeric data. Whether data is numeric is determined by inspecting the data

### REQ-102 (Requirement Type)
foo bar

### REQ-15 (Requirement Type)
The data will be imported into an existing ReqIF model as a new Specification. The user can use drag and drop to move the data elsewhere.

# Specification
- Description: Solution

## R23 (Headline Type)
Solution

### REQ-103 (Requirement Type)
Realize it this way

## R14 (Headline Type)
