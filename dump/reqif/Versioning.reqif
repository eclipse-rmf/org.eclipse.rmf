# ProR Versioning Support

# Specification: Specification Document
- Description: ProR Versioning Support

## R2 (Headline Type)
Versioning for ProR

### REQ-1 (Requirement Type)
As part of ProR essentials, we will implement versioning support for ProR.  This document gathers requirements and describes the relevant use cases.

## R3 (Headline Type)
General Requirements

### REQ-2 (Requirement Type)
Once configured, users do not need (but may) to take action to manage the data in the repository.

### REQ-8 (Requirement Type)
Must manage embedded files.

## R5 (Headline Type)
Architectural Decisions

### REQ-3 (Requirement Type)
A preliminary analysis of available technologies revealed the following four technologies:

#### REQ-4 (Requirement Type)
EMF-Compare: A Diff/Merge tool.  Interoperates with several version stores (svn, git, etc.).  We have experience thanks to the Camille Editor for Rodin.

##### REQ-29 (Requirement Type)
Since, the most version stores follows a different mechanism for instance for commands like checkout, commit, add etc.,, we have decided that the tool shall provide an interface for implementing different version stores

#### REQ-7 (Requirement Type)
EMF Diff/Merge: An alternative engine, using the EMF Compare GUI.  Worrysome is the low activity.

#### REQ-5 (Requirement Type)
EMF Store: Requires its own Repository, but ships with powerful GUIs.

#### REQ-6 (Requirement Type)
ReqIF Server: While ReqIF server provides a number of attractive features, especially with respect to versioning, it does provide an Eclipse-based Diff/Merge UI.  In addition, it is a commercial product which makes it difficult to offer as part of Essentials.  Last, the creation of an adapter would require a significant amount of work.

### REQ-9 (Requirement Type)
At this point, EMF Compare seems to be the technology of choice: We have experience working with it, and we can produce results quickly.  In addition, it offers a lot of flexibility, as it is not tied to a repository technology.  An issue could be performance.

#### REQ-28 (Requirement Type)
While EMF Compare evaluated so far we identified that there is no integrated support for resolving conflicts from a versioning system like Subversion and GIT. However, EMF Compare supports already a three-way-merge that can be used programmatically. For instance, subversion generates in case of a merge conflict three different files (base, version1 and version2) which can be used for feeting the three-way-merge mechanism of EMF Compare. However, there are several other things that have to be considered:

- Subversion adds markers in the original file (this leads to errors when opening the file, cause the XML structure is not well formed anymore)
- If using the three-way-merge mechanism from EMF compare we have to port the merged one to the original one
- Starting the three-way-merging should be transparent for the user, this means that the tool should autoamtically start the merge with the three different files generated by subversion

## R13 (Headline Type)
Use Case: Opening a project / Launching ProR

### REQ-10 (Requirement Type)
The user opens a project. Open a project means ...
- Actors: User

#### REQ-41 (Requirement Type)
(1) The user launchs ProR
- Done: Done
- Actors: User

#### REQ-42 (Requirement Type)
(2) The user opens manually a project via right clickt -> Open Project (as a consequence the project must be closed before!)
- Actors: User

### REQ-51 (Requirement Type)
ProR asks the user whether the local files should be updated from the repository first
- Done: Done
- Actors: ProR

### REQ-11 (Requirement Type)
ProR gives the user the the option to answer yes/no, and to mark that as the default, in which case the question will not be posed any more for that project.
- Done: Done
- Actors: ProR

#### REQ-12 (Requirement Type)
If multiple projects are being opened at the same time (for instance, upon launching ProR), the question is posed for every project.  We should consider aggregating these requests into one UI.
- Done: Done
- Actors: ProR

##### REQ-38 (Requirement Type)
Question: Should we show a message which informs the user which projects were updated anyway (although the user marked the update mechanism as default)?
- Done: Question (!)

### REQ-13 (Requirement Type)
If a merge conflict happens: ProR informs the user. The Project View will show the conflict information, and users will have to take action to resolve the conflict.
- Actors: ProR

### REQ-62 (Requirement Type)
The user has every time the option to change this setting via the project properties (right click on project -> Properties)
- Done: Done
- Actors: User

## R19 (Headline Type)
Use Case: Closing a project / Closing ProR

### REQ-14 (Requirement Type)
The user closes a project. Closing a project means ...
- Actors: User

#### REQ-43 (Requirement Type)
(1) The user closes ProR
- Actors: User

#### REQ-44 (Requirement Type)
(2) The user closes manually a project via right clickt -> Close Project (as a consequence the project must be opened before!)
- Actors: User

### REQ-54 (Requirement Type)
If local changes exist: ProR asks the user whether the local changes should be committed to the repository.
- Actors: ProR

#### REQ-15 (Requirement Type)
Users have the option to answer yes/no, and to mark that as the default, in which case the question will not be posed any more for that project.
- Actors: User

### REQ-46 (Requirement Type)
If multiple projects are being closed at the same time (for instance, upon closing ProR), the question is posed for every project.  We should consider aggregating these requests into one UI.
- Actors: ProR

#### REQ-64 (Requirement Type)
Question: What commit message should be used, or should the user have the option to enter a custom commit message?
- Done: Question (!)

### REQ-16 (Requirement Type)
Before doing the push, the system will perform a pull, which may result in a merge conflict.  In that case, ProR informs the user and gives the option to close the project anyway, or to cancel, so that the conflicts can be resolved.
- Actors: ProR

### REQ-61 (Requirement Type)
The user has always the option to change this setting via the project properties (right click on project -> Properties)
- Actors: User

## R61 (Headline Type)
Use Case: Closing a ReqIF file

### REQ-55 (Requirement Type)
The user closes a ReqIF File. Closing means, that the user closes the Specification Editor.
- Actors: User

### REQ-56 (Requirement Type)
ProR check whether the ReqIF model was changed by the user.
- Actors: ProR

### REQ-57 (Requirement Type)
If local changes exist: ProR asks the user whether the local changes should be committed to the repository. In this case the whole project which includes the affected ReqIF file will be commited.
- Actors: ProR

### REQ-59 (Requirement Type)
If multiple ReqIF files are being closed at the same time (for instance, via the action "Close all"), the question is posed for every project which includes the affected ReqIF file. If for instance two files of the same project are closed at the same time, the question is only posed one time for the project. We should consider aggregating these requests into one UI.
- Actors: ProR

#### REQ-60 (Requirement Type)
Question: What commit message should be used, or should the user have the option to enter a custom commit message?
- Done: Question (!) -> see comment
- Comment: (mj) One option would be to show this in a view.  If the view is hidden, make it visible.  I was hoping that we could reuse a standard view from Eclipse, but I could not find one that's appropriate.

### REQ-58 (Requirement Type)
Before doing the commit, the system will perform an update, which may result in a merge conflict.  In that case, ProR informs the user.
- Done: > see comment
- Actors: ProR
- Comment: Same approach as suggested for REQ-60 could be used.

### REQ-63 (Requirement Type)
The user has always the option to change this setting via the project properties (right click on project -> Properties)
- Actors: User

### R55 (Headline Type)
Use Case: Add Files to Project

#### REQ-48 (Requirement Type)
The user adds a new file to the project. Adding a new file means ...
- Actors: User

##### REQ-49 (Requirement Type)
(1) The user adds a new external file (for instance a word file, image file, etc.) to the project
- Actors: User

##### REQ-50 (Requirement Type)
(2) The user creates a new ReqIF File in the project
- Actors: User

#### REQ-20 (Requirement Type)
ProR adds automatically (the command "add" of the specific version management system in order to add the change to the next commit) new files (reqif files as well as external files like word, excel documents, etc.)  in the project into the repository.
- Actors: ProR

#### REQ-65 (Requirement Type)
The user has always the option to change this setting via the project properties (right click on project -> Properties)
- Actors: User

## R27 (Headline Type)
Use Case: Inspect History

### REQ-21 (Requirement Type)
The repository's Hsitory Viewer is used for inspecting the History.
- Done: Done
- Actors: User

### REQ-22 (Requirement Type)
It has to be ensured that the ProR Diff tool is launched, when a comparision is requested.
- Done: Done
- Actors: ProR

## R30 (Headline Type)
Use Case: Compare Models

### REQ-23 (Requirement Type)
Three GUIs for comparing are conceivable.  Which ones will be implemented is not clear yet.  These are:

### REQ-24 (Requirement Type)
(1) Compare by ReqIF model structure: Such a tool would use the ReqIF structure (rather than the ones used in the GUI) to compare models.  That means that changes in a SpecObject's value do NOT appear in the Specification, but in the ReqIFContent.

### REQ-25 (Requirement Type)
(2) Simplified Compare Specifications: This would be a side-by-side view of the Specifications.  An idea is to only show those Columns that hold Attributes that actually changed.  This would be intuitive and useful, but would not show changes to the Datatypes and other aspects of the model.

### REQ-26 (Requirement Type)
(3) List of changes: This view would state, as a list, all the changes between models.  This could be useful when there are only a few changes.

## R35 (Headline Type)
Use Case: Merge Models

### REQ-27 (Requirement Type)
This GUI would provide a three-way comparison that allows to cherry-pick changes.  It would be based on the ReqIF Model.

## R22 (Headline Type)
Use Case: Save Actions (Deprecated!?)

### REQ-17 (Requirement Type)
Users are given the option to configure save action on a per-project basis:

#### REQ-40 (Requirement Type)
Question: Save action in the specification editor (reqif files). What is with external files which are related to the reqif project?
- Done: Question -> see comment
- Comment: I'd argue that this applies to all files in the project.  It may be possible to register a project listener for this.

### REQ-18 (Requirement Type)
(1) Perform a pull/update upon save

### REQ-19 (Requirement Type)
(2) Perform a push upon save.  In that case, it will be preceeded by a mandatory pull.

#### REQ-37 (Requirement Type)
Question: What commit message should be used, or should the user have the option to enter a custom commit message?
- Done: Question -> see comment
- Comment: Good quesiton.  This is one of those things that can easily be extended later.  So maybe we should break this into two requirements: (1) The ability to do this in the first place, and (2) the customization of the commit message.

## R73 (Headline Type)
Use Case: Enable a project for Versioning

### REQ-66 (Requirement Type)
There is a project option (context menu?) to enable versioning for a project

### REQ-67 (Requirement Type)
Once triggered, a wizard starts.

### REQ-68 (Requirement Type)
Optional: If the project is not yet managed by subversive, help the user configure subversive (for instance, by launching the subversive wizard, if launching a wizard from a wizard is possible...)

### REQ-69 (Requirement Type)
Allow the user to configure the plugin's behavior.

### REQ-70 (Requirement Type)
Once completed, the Versioning function is enabled for the project

# Specification
- Description: Todo

## R39 (Headline Type)
TODO

### REQ-30 (Requirement Type)
This is a list of tasks for the end of octobre (the first tasks are to be prioritized)

#### REQ-31 (Requirement Type)
Adapt the match engine of EMF Compare (for instance that the engine compares the IDs of specific ReqIF elements)

Furthermore ... 
- We should try to ignore the ordering of specobjects (when changed)
- We should ignore the las modified date attribute (when changed)

In addition, we should create a catalogue of items with irrelevant differences and acceptable differences

#### REQ-32 (Requirement Type)
Remove dialog that always popups then comparing two ReqIF files (nerved)

#### REQ-34 (Requirement Type)
Implement save, open, close use cases (automatic syncronization with repository). This task includes to create a clean interface for the different version management systems.

#### REQ-35 (Requirement Type)
Support diff of external files in compare/diff view

#### REQ-33 (Requirement Type)
Adapt icons in item providers --> Take icons from the original ProR plugin (org.eclipse.rmf.pror.reqif10.edit)

#### REQ-36 (Requirement Type)
Implement three-way-mergin of subversion generated conflicts
