# Specification: Specification Document
- Description: Requirements Document

## GOAL (Requirement Type)
The goal is to develop an approach for the ProR Essentials documentation. In the first step we gather the requirements and in the second step we evalutate possible approaches. We identify we pros and cons of the several approaches and face them to the requirements.

## R4 (Headline)
Requirements

### REQ-1 (Requirement Type)
The documentation shall be hosted online

### REQ-2 (Requirement Type)
The documentation shall be provided as an Eclipse Help Plugin

#### REQ-18 (Requirement Type)
We need one Eclipse Help Plugin for each project like Diff Tool, Versioning, Rodin Integration

### REQ-3 (Requirement Type)
Consider to use the online hosted documentation as Project Website (e.g. for commercial purposes and also for the correct audience)

### REQ-5 (Requirement Type)
Distinguish between user documentation and developer documentation. There are two different target audience!

## R10 (Headline)
Specification

### REQ-4 (Requirement Type)
Idea

#### REQ-6 (Requirement Type)
The Wiki approach
- links to -> R8

##### REQ-7 (Requirement Type)
We maintain three different Wiki pages: ProB, BMotion Studio and ProR Essentials

##### REQ-9 (Requirement Type)
For ProB and BMotion Studio wiki websites already exsits, we only need to create a new one for the ProR Essentials Project.

##### REQ-8 (Requirement Type)
We should keep the design/layout of the three websites consistent. I propose to use the design/layout of the Formal Mind webpage.

###### REQ-10 (Requirement Type)
The design/layout of the ProB and BMS wiki site needs to be adapted.

##### REQ-14 (Requirement Type)
Create subdomains like: prob.formalmind.com, bms.formalmind.com, pror.formalmind.com and link them to the different wiki pages

### REQ-11 (Requirement Type)
Implementation

#### REQ-12 (Requirement Type)
Step 1: Create a new Wikipage for the ProR Essentials Project

#### REQ-13 (Requirement Type)
Step 2: Adapt the Formal Mind Design to the Wiki Page

#### REQ-15 (Requirement Type)
Step 3: Create a suitable structure for the documentation/site

#### REQ-16 (Requirement Type)
Step 4: Migrate current content (FM Blog, Event-B Wiki to the new site)

#### REQ-17 (Requirement Type)
Step 5: Create a jenkins job in order to create automatically the different Eclipse Help Plugins for the different sub projects (diff, versioning, rodin integration)

# Specification
- Description: Approach Evaluation

## R5: Rodin Handbook Approach (Approach)
The Rodin Handbook is maintained in latex. A Jenkins job generates a HTML Browsable document, an Eclipse Help Plugin and a PDF Document.
- Pros: - Many available formats: PDF, Eclipse Help Plugin, HTML
- Cons: - Cumbsersome to edit and maintain

## R6: Drupal Approach (Approach)
Drupal is the software used by our Formal Mind Website. Drupal is modular and can be extended , i.e. for documentation purposes.
- Cons:
  - Needs to implement an approach for automatically generating an Eclipse Help Plugin
  - Mixing Tool stuff with company information
- Pros: - Direct reference to Formal Mind Webpage/Company

## R7: Redmine Approach (Approach)
Redmine is our Formal Mind Bug Tracker.
- Pros:
  - A hierachical structure with the several ProR Essentials projects already exists
  - Modules, like a Wiki module already exsits
- Cons:
  - Mixing developing stuff with user content
  - An industrial/normal user can be confused of such things like "bugs" etc., if we use this documentation/project site for commercial reasons

## R8: Wiki Approach (Approach)
Create a new Wiki Page especially for the ProR Essentials Project
- Pros:
  - Easy to create automatically an Eclipse Help Plugin
  - Direct editing on website
  - Consistency: Currently we have a Wiki Website for the ProB Tool and the BMotion Studio Tool
- Cons:
  - No consistent design. Mabye we need to adapt the design of the three wiki pages (ProB, BMS, ProR Essentials)
    --> Need to check if we can use the Formal Mind design for fir purpose (check license)
