# Specification: Specification Document
- Description: Requirements Document

## R2 (Headline Type)
ProR Search and Replace

### REQ-1 (Requirement Type)
This document specifies a search and replace feature for ProR.

## R3 (Headline Type)
High-level Goals

### REQ-2 (Requirement Type)
As a user, I want to be able to search in a "standard fashion".

### REQ-3 (Requirement Type)
As a user, I want to be able to replace in a "standard fashion".

### REQ-4 (Requirement Type)
"standard fashion" in this case means in an intuitive manner that is standard for the platform (in this case Eclipse).

### REQ-5 (Requirement Type)
As a user, I want to be able to use searches for filtering.

## R33 (Headline Type)
User Stories

### REQ-40 (Requirement Type)
As a user, I want to find specific text sniplets anywhere

### REQ-41 (Requirement Type)
As a user, I want to search for specific attributes.

### REQ-42 (Requirement Type)
As a user, I want to selectively replace text or attributes.

### REQ-43 (Requirement Type)
As a user, I want limit what I see according to certain filter criteria.

## R8 (Headline Type)
Implementation Considerations

### REQ-6 (Requirement Type)
Obviously, existing technologies shall be used as much as possible.  Candidates identified so far include:

#### REQ-7 (Requirement Type)
EMF Search (suggested by Hussein).  However, EMF Search seems to be dead, according to https://wiki.eclipse.org/EMF_Search

#### REQ-8 (Requirement Type)
Standard Eclipse Search.  Note that Eclipse Search already works "out of the box", using the "file search".  But the search interface only accepts text, and the result shows the corresponding XML line.  So to use this, both search interface and result view would need to be improved.

#### REQ-34 (Requirement Type)
Please add any others that may be of interest.

## R12 (Headline Type)
User Interface Elements

### REQ-9 (Requirement Type)
The following User Interface Views are required to support the user cases:

### R14 (Headline Type)
Search Query View

#### REQ-10 (Requirement Type)
The Query View allows the user to construct search criteria.

#### REQ-18 (Requirement Type)
The Query View is intended for SpecElementsWithAttributes.  In other words, other Elements like Datatypes, etcs. are not considered.

#### REQ-11 (Requirement Type)
NOTE: We have a few options here, the following is one suggestion.

#### REQ-12 (Requirement Type)
A Query consists of QueryElements.  The user Interface allows QueryElements to be added and removed.

#### REQ-13 (Requirement Type)
A QueryElement consists of three parts: QueryTarget, QueryOperator, QueryValue

#### REQ-14 (Requirement Type)
The QueryElement narrows the AttributeValue(s) to be considered: This could be: (1) any value; (2) any value of a given SpecType; (3) any value with a given AttributeName; (4) a specific attribute.

#### REQ-15 (Requirement Type)
The QueryOperator defines how matching should take place.  For an initial implementation, I suggest to only offer "RegExp".  Obviously, this is challenging for novice users.  For this to work, all Attributes have to be converted to Strings.  This has already been implemented for the Quick Search feature, so check there.  For XHTML, all formatting will be ignored.

#### REQ-16 (Requirement Type)
In case of "specific attribute" (where implicitly the type is known), instead of RegExp, we can offer type-specific search (e.g. a range for numbers, etc.)  Implementation of this can be postponed.

#### REQ-19 (Requirement Type)
Alternatives to ReqIF could be "exact match", "match substring", "inverse match".

#### REQ-17 (Requirement Type)
For a match, all QueryElements are combined via "AND".

#### REQ-26 (Requirement Type)
I anticipate Search Query Views to be used in more than one context.  Initially, it will be part of the Search | Search... dialog (as a new tab, "ReqIF Search").  But later, I expect it to be used for defining filters.  This means, amongst other things, that searches must be persistable, and it must be possible to repopulate a Search Query View with a saved query, for editing.

### R15 (Headline Type)
Search Result View

#### REQ-20 (Requirement Type)
The Search Result View shall show the matches in a tree structure, as is typically done.

#### REQ-21 (Requirement Type)
However, the tree structure shall be the same as shown in the Outline: E.g. a match in a SpecRelation is shown as a child of the "SpecRelations" folder.  Matching SpecObjects shall be shown as a child of "SpecObjecsts", as well as a child of "Specifications" (if a SpecHierarchy exists that references the SpecObject.

#### REQ-22 (Requirement Type)
Underneath the category folder, the SpecElement shall be shown with the correct icon (SpecObject, Specification, SpecRelatio, SpecRelationGroup) and the correct label.

#### REQ-23 (Requirement Type)
Underneath the Element, the match is shown, which is a text representation of the matching AttributeValue.

#### REQ-24 (Requirement Type)
Bonus 1: Highlight the match
Bonus 2: If more than one Value matches, show all matching Values.

### R35 (Headline Type)
Replace View

#### REQ-27 (Requirement Type)
I suggest that we permit "Replace" only if the user has exactly one QueryElement with "a specific attribute".  As for replace, we need to know the type (unless we want to make things really sophisticated).

#### REQ-28 (Requirement Type)
There is a replace button on the Search dialog, which is only enabled for the above criteria.

#### REQ-29 (Requirement Type)
Upon hitting "Replace", the user can select the replacement value, which is type dependent:

##### REQ-30 (Requirement Type)
String: only the matching text will be replaced.

##### REQ-31 (Requirement Type)
XHTML: only matching ttext will be replaced.  If the match contains formatting, it will be lost.

##### REQ-32 (Requirement Type)
Integer, REal, Date, Boolean: Replace only

##### REQ-33 (Requirement Type)
Enumerations: if it is a multi-value enumeration, offer to add-only (e.g. those selected will be checked, all others ignored), remove only (e.g. only those unchecked will be cleared, all others ignored), or set exactly.

### R31 (Headline Type)
Optional: Quick Search in Datatype Dialog

#### REQ-25 (Requirement Type)
It would be useful to have a "Quick Search" feature in the Datatype Configuration Dialog.

### R44 (Headline Type)
Optional: Filter View

#### REQ-35 (Requirement Type)
The Filter View is a Dialog that shows the user a list of named Search Queries.

#### REQ-36 (Requirement Type)
The user can edit search queries, rename them, copy them and delete them.

### R48 (Headline Type)
Filter Control

#### REQ-37 (Requirement Type)
If we implement a Filter View, we also need a way to appy it.  The filter control is part of the Toolbar.

#### REQ-38 (Requirement Type)
The filter control, when activated, shows a list of all filters (by name).  The user can select one ore more filters. Multiple filters will be combined via OR. (NOTE: This way, users have the flexibility to create QueryElements that are combined via AND in Filters, and combining filters via OR).

#### REQ-39 (Requirement Type)
Filters are applied on the complete Model, meaning that they apply to all Specifications and the Outline.
