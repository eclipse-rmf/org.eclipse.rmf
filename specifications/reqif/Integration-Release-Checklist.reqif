# Specification: Specification Document
- Description: Integration Release Checklist

## R4 (Headline)
Integration-Release Checklist

## R5 (Information)
This document lists all tasks that need to be done upon creating a new integration release.

## R6 (Information)
When preparing a new release, all items for the given release must be set to "done".

## R7 (Headline)
Preparing an Integration-Release

## R8 (Information)
To prepare a release, perform the following steps:

### R9 (Information)
Edit the Datatype and add a new attribute, named after the build (e.g. 0.4.0).  Give it the status type.

### R10 (Information)
Remove older releases from the specification editor (they will still be visible through the properties view)

### R11 (Information)
Add the current release to the specification view.

## R12 (Headline)
Checklist

### R1 (Requirement Type)
All plug-ins have the correct version number

### R2 (Requirement Type)
The About... dialog has the correct version number

### R3 (Requirement Type)
The wizard creates a model with the correct version number

## R13 (Headline)
GUI-Tests

### R14 (Requirement Type)
Perform Drag & Drop
- Expected: Elements should be moved.  Depending on drop position, they should be inserted as siblings or children.

### R15 (Requirement Type)
Create link with drag and drop

### R16 (Requirement Type)
Set a type, the values should be update

### R17 (Requirement Type)
Try printing, using a spec that uses the Headline Configuration (like this one)
- Expected: Check in particular the formatting of the headlines.
