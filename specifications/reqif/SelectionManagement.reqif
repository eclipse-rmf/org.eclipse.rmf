# Specification: Specification Document
- Description: Behavior

## R1 (Headline Type)
- Action: Desired Behavior

## REQ-104 (Requirement Type)
- Action: The user clicks on a cell foo
- Behavior: Globally, the given SpecElement is selected

## REQ-105 (Requirement Type)
- Action: New cell added. and edited.

## REQ-107 (Requirement Type)
- Action: Forth

## R6 (Headline Type)
- Action: Outline

### REQ-108 (Requirement Type)
- Action: Editor activated
- Behavior: Outline updates

### REQ-109 (Requirement Type)
- Action: Outline clicked
- Behavior: Initially: Nothing
  Optional: visible editor updates

## REQ-106 (Requirement Type)
- Action: Fooo
