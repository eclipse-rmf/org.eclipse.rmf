# Specification: Specification Document
- Description: Requirements Document

## R5: User-Friendly Searcing Title (Requirement Type)

### R1 (Requirement Type)
While there is very basic search support available, it is currently not suitable for professional work.  The objective of this project is to improve this, as follows:

### R7: Search-UI (Requirement Type)

#### R2 (Requirement Type)
The following is a proposal on how the interface could look like, based on best practices in user interface design.
- Status: Done
- Integer: 1

#### R6 (Information Type)
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
#### R8 (Requirement Type)
Note that this is a non-functional mock-up.  The final interface will differ in appearance.
- Status: Done

#### R9 (Requirement Type)
The final Details regarding the conditions are found after this table in “Search Conditions” below. interface will differ in appearance.
- Status: Done

#### R10 (Requirement Type)
The search interface allows the user to to configure a number of “conditions”.  These relate either to internal attributes (e.g. internal ID) or attribute values (those attributes that the user creates), with typical type-specific relations: equal, contains, etc.
- Status: Done

#### R11 (Requirement Type)
All conditions are combined via “and” or “or”.  More complex relationships are not supported in this first implementation. Details regarding the conditions are found after this table in “Search Conditions” below.
- Status: Done

### R12: Spec-Nav (Requirement Type)

#### Spec-Nav (Requirement Type)
Within a Specification, users can navigate between search results via corresponding buttons in the toolbar, i.e. .  Note that this will not cycle through elements outside the specification (e.g. elements in other Specifications or SpecTypes).
- Status: Done

#### R13 (Information Type)
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
### R14: Result-Nav (Requirement Type)

#### Result-Nav (Requirement Type)
The result of a search will be shown in a separate view, as shown in the mockup (implementation appearance may vary).
- Status: Done

#### R19 (Information Type)
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
#### R15 (Requirement Type)
In will show all matches, including those that are not accessible from the Specification Editor.
- Status: Done

#### R16 (Requirement Type)
The View will exhibit the following behavior:

#### R17 (Requirement Type)
Selecting any element will show its properties in the Properties View, where it can be edited.
- Status: Done

#### R18 (Requirement Type)
Double-Clicking on a SpecHierarchy will open the corresponding Specification, with the clicked SpecHierarchy selected.
- Status: Done

### R20: Search-Conditions (Requirement Type)

#### R21 (Requirement Type)
In the following, we outline the various Conditions for the search box.

#### R22 (Requirement Type)
The Scope of attributes can be “internal” or “value”.
- Status: Done

#### R23 (Requirement Type)
Internal attributes are those defined by the ReqIF standard, e.g. Identifiable.identifier.
- Status: Done

#### R24 (Requirement Type)
Values are specific instances of Attributes that were set up by the user. They are identified in the form SPECTYPE.ATTRIBUTENAME.  Thus, as users create new SpecTypes and their attributes, so will the list of choices grow.
- Status: Done

#### R25 (Requirement Type)
The available criteria are determined by the Type.  We can class multiple attributes in one type (e.g. integer and real are both of type NUM).
- Status: Done

#### R26 (Requirement Type)
If an attribute is null or does not exist, then it is treated as if it was empty.
- Status: Done

#### R27 (Requirement Type)
Identifiable.identifier (STRING): Internal attribute
- Status: Done

#### R28 (Requirement Type)
Identifiable.lastChange (DATE): Internal attribute
- Status: Done

#### R29 (Requirement Type)
Identifiable.desc (STRING): Internal attribute
- Status: Done

#### R30 (Requirement Type)
Identifiable.longName (STRING) Internal attribute
- Status: Done

#### R31 (Requirement Type)
AttributeValueBoolean (BOOL): Value
- Status: Done

#### R32 (Requirement Type)
AttributeValueDate (DATE): Value
- Status: Done

#### R33 (Requirement Type)
AttributeValueEnumeration (ENUM): Value
- Status: Done

#### R34 (Requirement Type)
AttributeValueInteger (NUM): Value
- Status: Done

#### R35 (Requirement Type)
AttributeValueReal (NUM): Value
- Status: Done

#### R36 (Requirement Type)
AttributeValueString (STRING): Value
- Status: Done

#### R37 (Requirement Type)
AttributeValueXHTML (XHTML): Value
- Status: Done

#### R38 (Requirement Type)
The following table describes the various types.  Most types are straight forward, except XHTML.
- Status: Done

#### R39 (Requirement Type)
The XHTML operation is applied to the raw XHTML, including all tags (this allows searching for embedded URLs, for instance).  There is the additional option of “regexp plain”. In that case, the regular expression is applied to the plain text, with all tags stripped out.
- Status: Done

#### R40 (Requirement Type)
NOTE: We are considering to introduce a NEGATION flag for all conditions.  This would reduce the number of selectors, but of course not the number of overall options.
- Status: Won't implement

### R75: Operators for all (Requirement Type)

#### R76 (Requirement Type)
is set: If a non-null-value exists, return true.  Ignore default values (i.e. if there is a default value but no explicitly set one, return false).
- Status: Done

#### R77 (Requirement Type)
is not set: return true only if the attribute exisits, but is not set (irrespective of default value).
- Status: Done

### R41: Search-Conditions Interface (Requirement Type)

#### R42: String (Requirement Type)
- Status: Done

##### R43 (Requirement Type)
equal:one text field (if empty: false)
- Status: Done

##### R44 (Requirement Type)
not equal: one text field (if empty: true)
- Status: Done

##### R45 (Requirement Type)
contains: one text field (if empty: false)
- Status: Done

##### R46 (Requirement Type)
not contains: one text field (if empty: true)
- Status: Done

##### R47 (Requirement Type)
regexp: one text field (if empty: regexp applied to empty string)
- Status: Done

#### R48: Date (Requirement Type)
- Status: Done

##### R49 (Requirement Type)
is: one date selector (if empty: false)
- Status: Done

##### R50 (Requirement Type)
is not: one date selector (if empty: true)
- Status: Done

##### R51 (Requirement Type)
between: two date selectors (if empty: false)
- Status: Done

##### R52 (Requirement Type)
before: one date selector (if empty: false)
- Status: Done

##### R53 (Requirement Type)
after: one date selector (if empty: false)
- Status: Done

#### R54: Bool (Requirement Type)
- Status: Done

##### R55 (Requirement Type)
is: dropwdown: true/false (if empty: false)

#### R56: Number (Requirement Type)
- Status: Done

##### R57 (Requirement Type)
is: one number field (if empty: false)
- Status: Done

##### R58 (Requirement Type)
is not: one number field (if empty: true)
- Status: Done

##### R59 (Requirement Type)
between: two number fields (if empty: false)
- Status: Done

##### R60 (Requirement Type)
greater: one number field (if empty: false)
- Status: Done

##### R61 (Requirement Type)
smaller: one number field (if empty: false)
- Status: Done

#### R62: XHTML (Requirement Type)
- Status: Done

##### R63 (Requirement Type)
contains: one text field (if empty: false)
- Status: Done

##### R64 (Requirement Type)
not contains: one text field (if empty: true)
- Status: Done

##### R65 (Requirement Type)
regexp: one text field (if empty: regexp applied to empty string)
- Status: Done

##### R66 (Requirement Type)
regexp plain: one text field (if empty: regexp applied to empty string)
- Status: Done

#### R67: Enum (Requirement Type)
- Status: Done

##### R68 (Requirement Type)
equal: multiple choice (if empty: false, unless empty)
- Status: Done

##### R69 (Requirement Type)
not equal: multiple choice (if empty: true, unless empty)
- Status: Done

##### R70 (Requirement Type)
contains all: multiple choice (if empty: false, unless empty)
- Status: Done

##### R71 (Requirement Type)
contains any: multiple choice (if emtpy: false, unless empty)
- Status: Done

### R72: Documentation (Requirement Type)

#### R73 (Requirement Type)
Context-Sensitive Integration
- Status: Done

#### R74 (Requirement Type)
Help Content
- Status: Ready
